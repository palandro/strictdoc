[DOCUMENT]
TITLE: Untitled

[REQUIREMENT]
UID: REQ-001
CAPELLA_IE_OBJECT_TYPE: DT-IOT-REQ-f72a872b-21e8-4c76-98af-467ddc9d8355
CAPELLA_REQ_UUID: d605e695-2e39-4c92-b863-d096162e0014
CAPELLA_REQ_NAME: Flight modes
CAPELLA_REQ_LONG_NAME: Null
CAPELLA_REQ_DOC_URL: "../../../system_architecture/output/test/d605e6952e394c92b863d096162e0014.html"
CAPELLA_ALLOCS_1_UUID: f9cabb24-100b-4e68-930a-8f35ec38c106
CAPELLA_ALLOCS_1_NAME: Watch Movie
CAPELLA_ALLOCS_1_LONG_NAME: Null
CAPELLA_ALLOCS_1_DOC_URL: "../../../system_architecture/output/test/f9cabb24100b4e68930a8f35ec38c106.html"
TITLE: Flight modes
STATEMENT: >>>
The system X shall do Y.
<<<
